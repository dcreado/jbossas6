-- This MIB Generated by the JBoss MIB Generator

JBOSS-AS-MIB DEFINITIONS ::=BEGIN

IMPORTS
	OBJECT-TYPE,
	NOTIFICATION-TYPE,
	Counter32,
	Gauge32,
	Counter64,
	TimeTicks
		FROM SNMPv2-SMI
	DisplayString,
	TruthValue
		FROM SNMPv2-TC;

jbossAsObjects		OBJECT IDENTIFIER ::= { 1 3 6 1 4 1 2312 100 1 1 }
testTableDefinition		OBJECT IDENTIFIER ::= { 1 3 6 1 4 1 2312 100 1 301 }
system		OBJECT IDENTIFIER ::= { 1 3 6 1 2 1 1 }

activeThreadCount OBJECT-TYPE
	SYNTAX INTEGER
	ACCESS read-only
	STATUS current
	DESCRIPTION 
		"The amount of active threads the server is handling."
::= { jbossAsObjects 1 }

freeMemory OBJECT-TYPE
	SYNTAX OCTET STRING (SIZE(0..255))
	ACCESS read-only
	STATUS current
	DESCRIPTION 
		""
::= { jbossAsObjects 2 }

maxMemory OBJECT-TYPE
	SYNTAX OCTET STRING (SIZE(0..255))
	ACCESS read-only
	STATUS current
	DESCRIPTION 
		""
::= { jbossAsObjects 3 }

inUseConnectionCount OBJECT-TYPE
	SYNTAX OCTET STRING (SIZE(0..255))
	ACCESS read-only
	STATUS current
	DESCRIPTION 
		""
::= { jbossAsObjects 9 }

maxConnectionsInUseCount OBJECT-TYPE
	SYNTAX OCTET STRING (SIZE(0..255))
	ACCESS read-only
	STATUS current
	DESCRIPTION 
		""
::= { jbossAsObjects 10 }

instantiationTime OBJECT-TYPE
	SYNTAX DisplayString
	ACCESS read-only
	STATUS current
	DESCRIPTION 
		""
::= { jbossAsObjects 7 }

trapCount OBJECT-TYPE
	SYNTAX DisplayString
	ACCESS read-only
	STATUS current
	DESCRIPTION 
		""
::= { jbossAsObjects 11 }

bindAddress OBJECT-TYPE
	SYNTAX DisplayString
	ACCESS read-only
	STATUS current
	DESCRIPTION 
		""
::= { jbossAsObjects 12 }

sysDescr OBJECT-TYPE
	SYNTAX OCTET STRING (SIZE(0..255))
	ACCESS read-write
	STATUS current
	DESCRIPTION 
		""
::= { system 1 }

sysObjectId OBJECT-TYPE
	SYNTAX OCTET STRING (SIZE(0..255))
	ACCESS read-only
	STATUS current
	DESCRIPTION 
		""
::= { system 2 }

sysUpTime OBJECT-TYPE
	SYNTAX OCTET STRING (SIZE(0..255))
	ACCESS read-only
	STATUS current
	DESCRIPTION 
		""
::= { system 3 }

sysContact OBJECT-TYPE
	SYNTAX OCTET STRING (SIZE(0..255))
	ACCESS read-only
	STATUS current
	DESCRIPTION 
		""
::= { system 4 }

sysName OBJECT-TYPE
	SYNTAX OCTET STRING (SIZE(0..255))
	ACCESS read-only
	STATUS current
	DESCRIPTION 
		""
::= { system 5 }

sysLocation OBJECT-TYPE
	SYNTAX OCTET STRING (SIZE(0..255))
	ACCESS read-only
	STATUS current
	DESCRIPTION 
		""
::= { system 6 }

sysServices OBJECT-TYPE
	SYNTAX OCTET STRING (SIZE(0..255))
	ACCESS read-only
	STATUS current
	DESCRIPTION 
		""
::= { system 7 }

webappDefaultMetricsTable OBJECT-TYPE
	SYNTAX	SEQUENCE OF WebappDefaultMetricsEntry
	MAX-ACCESS	not-accessible
	STATUS	current
	DESCRIPTION	
		"Table containing standard metrics for any webapp deployed on JBossAS"
::= { testTableDefinition 30 }

webappDefaultMetricsEntry OBJECT-TYPE
	SYNTAX	WebappDefaultMetricsEntry
	MAX-ACCESS	not-accessible
	STATUS	current
	DESCRIPTION
	""

		INDEX	{
		IMPLIED webappDefaultMetricsObjectName
		}
::= { webappDefaultMetricsTable 1 }		

WebappDefaultMetricsEntry ::= SEQUENCE {
	webappDefaultMetricsObjectName	DisplayString,
	webappDefaultMetricsDistributable	INTEGER,
	webappDefaultMetricsSessionCounter	INTEGER,
	webappDefaultMetricsActiveSessions	INTEGER,
	webappDefaultMetricsMaxActiveSessions	INTEGER,
	webappDefaultMetricsSessionAverageAliveTime	INTEGER,
	webappDefaultMetricsExpiredSessions	INTEGER,
	webappDefaultMetricsRejectedSessions	INTEGER,
	webappDefaultMetricsMaxInactiveInterval	INTEGER,
	webappDefaultMetricsSessionMaxAliveTime	INTEGER
}

webappDefaultMetricsObjectName OBJECT-TYPE
	SYNTAX DisplayString
	ACCESS not-accessible
	STATUS current
	DESCRIPTION 
		""
::= { webappDefaultMetricsEntry 1 }

webappDefaultMetricsDistributable OBJECT-TYPE
	SYNTAX INTEGER
	ACCESS read-only
	STATUS current
	DESCRIPTION 
		""
::= { webappDefaultMetricsEntry 2 }

webappDefaultMetricsSessionCounter OBJECT-TYPE
	SYNTAX INTEGER
	ACCESS read-only
	STATUS current
	DESCRIPTION 
		""
::= { webappDefaultMetricsEntry 3 }

webappDefaultMetricsActiveSessions OBJECT-TYPE
	SYNTAX INTEGER
	ACCESS read-only
	STATUS current
	DESCRIPTION 
		""
::= { webappDefaultMetricsEntry 4 }

webappDefaultMetricsMaxActiveSessions OBJECT-TYPE
	SYNTAX INTEGER
	ACCESS read-write
	STATUS current
	DESCRIPTION 
		""
::= { webappDefaultMetricsEntry 5 }

webappDefaultMetricsSessionAverageAliveTime OBJECT-TYPE
	SYNTAX INTEGER
	ACCESS read-only
	STATUS current
	DESCRIPTION 
		""
::= { webappDefaultMetricsEntry 6 }

webappDefaultMetricsExpiredSessions OBJECT-TYPE
	SYNTAX INTEGER
	ACCESS read-only
	STATUS current
	DESCRIPTION 
		""
::= { webappDefaultMetricsEntry 7 }

webappDefaultMetricsRejectedSessions OBJECT-TYPE
	SYNTAX INTEGER
	ACCESS read-only
	STATUS current
	DESCRIPTION 
		""
::= { webappDefaultMetricsEntry 8 }

webappDefaultMetricsMaxInactiveInterval OBJECT-TYPE
	SYNTAX INTEGER
	ACCESS read-only
	STATUS current
	DESCRIPTION 
		""
::= { webappDefaultMetricsEntry 9 }

webappDefaultMetricsSessionMaxAliveTime OBJECT-TYPE
	SYNTAX INTEGER
	ACCESS read-only
	STATUS current
	DESCRIPTION 
		""
::= { webappDefaultMetricsEntry 10 }

END
